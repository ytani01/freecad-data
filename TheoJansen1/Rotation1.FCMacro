import math
import FreeCAD as App
import FreeCADGui as Gui

actuator = App.ActiveDocument.getObjectsByLabel("Revolute")[0]

angle_init = 200
rotation_n = 3
angle_step = 10

for angle in range(angle_init, 360*rotation_n+angle_init, angle_step):
    # A full rotation of the Crank in steps of 10°
	
    actuator.Offset1.Rotation.Angle = math.radians(angle)
    App.ActiveDocument.recompute()
    Gui.updateGui()
